FME workspace unfoldconfusables.fmw

Parameters:
- SourceDataset_CSV2 = $(FME_MF_DIR)all_characters_confusables.csv   # Source CSV (Comma Separated Value) File(s)
- DestDataset_CSV2 = Z:\Projects\FYE2023\INS-54_GeneralTechnicalReadiness\inclusive-names-service\docs\test_data   # Destination CSV (Comma Separated Value) Folder

Readers:
- CSV2_1: CSV2 from $(SourceDataset_CSV2)

Writers:
- CSV2_2: CSV2 to $(DestDataset_CSV2)

CSV (reader CSV2_1)
    attributes: label string, id string, confusable_char string, confusable_unicode string
    -> AttributeKeeper
    -> AttributeKeeper_2
AttributeKeeper
    CREATE_BULK_MODE_FEATURES = NO
    KEEP_ATTRS = confusable_unicode,id,label
    -> AttributeSplitter
AttributeSplitter
    ATTR_NAME = confusable_unicode
    DELIMITER = ,
    DROP_EMPTY_PARTS = No
    LIST_NAME = unicode_list
    TRIM_OPTION = Both
    -> ListExploder
ListExploder
    ATTR_ACCUM_MODE = Merge List Attributes
    ATTR_CONFLICT_RES = Use List Attribute Values
    INDEX_ATTR = _element_index
    LIST_ATTR = unicode_list{}
    ELEMENTS -> Counter
Counter
    CNT_ATTR = _count
    DOMAIN = counter
    SCOPE = Local
    START = 0
    -> FeatureMerger [REQUESTOR]
AttributeKeeper_2
    CREATE_BULK_MODE_FEATURES = NO
    KEEP_ATTRS = confusable_char,id,label
    -> AttributeSplitter_2
AttributeSplitter_2
    ATTR_NAME = confusable_char
    DELIMITER = ,
    DROP_EMPTY_PARTS = No
    LIST_NAME = char_list
    TRIM_OPTION = Both
    -> ListExploder_2
ListExploder_2
    ATTR_ACCUM_MODE = Merge List Attributes
    ATTR_CONFLICT_RES = Use List Attribute Values
    INDEX_ATTR = _element_index
    LIST_ATTR = char_list{}
    ELEMENTS -> Counter_2
Counter_2
    CNT_ATTR = _count
    DOMAIN = counter
    SCOPE = Local
    START = 0
    -> FeatureMerger [SUPPLIER]
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> AttributeManager
AttributeManager
    ATTR_TABLE:
      RENAME_SET_VALUE label > char
      RENAME_SET_VALUE id > char_unicode
      REMOVE confusable_unicode
      RENAME_SET_VALUE unicode_list > confusable_unicode
      REMOVE _element_index
      REMOVE _count
      REMOVE confusable_char
      RENAME_SET_VALUE char_list > confusable
    -> confusables_unfolded (writer CSV2_2)
confusables_unfolded (writer CSV2_2)
    attributes: char string, char_unicode string, confusable_unicode string, confusable string
